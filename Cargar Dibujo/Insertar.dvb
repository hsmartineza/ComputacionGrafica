Attribute VB_Name = "Module1"
Sub extraerDatos()
    Dim libroDatos As Workbook
    Dim bl As AcadBlock
    Dim pto(0 To 2) As Double
    i = 1
    Set .libroDatos = Workbooks.Open("E:\OSCAR\UNAL\6to SEMESTRE\Computación Gráfica\Dibujo Sala CAD\Nuevos Dibujos\Excel.xlsx")
    Set bl = AutoCAD.Application.ActiveDocument.ModelSpace.InsertBlock(pto, "CPUCAD.dwg", 1, 1, 1, 0)
    Name = libroDatos.Sheets(1).Cells(1, 1)
    libroDatos.Close savechanges:=False
End Sub
